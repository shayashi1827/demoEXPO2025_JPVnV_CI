# DoorLockCntr_Reqs

## RQ-01: 自動ドアロック機能 (Container)
車両が走行状態になった場合に、ドアのロック指令を出力してほしい
- Rationale: 走行中にドアが開くと乗員が危険なため、自動的にロックして開かない状態にするため

### RQ-01-01: 走行時ロック機能 (Functional)
以下条件がいずれも成立した場合にロック要求指令を出力する。
・エンジン始動状態
・車両速度 > 5km/h が2秒継続

### RQ-01-02: 異常時アンロック機能 (Functional)
以下条件が成立した場合にアンロック要求指令を出力する。
・エアバック作動フラグ == ON

## RQ-02: ドアロックダイアグ機能 (Container)
ドアロック機構に何らかの異常がある場合、故障と判断し、ダイアグ信号要求を出力してほしい
- Rationale: 運転手がドアの異常に気付けるようにするため。

### RQ-02-01: ロックポジション判定条件 (Functional)
作動位置によってロックポジションを以下のように判定する。
・valが4mm以上 ⇒ ロック状態
・valが1mm以下 ⇒ アンロック状態
・上記以外 ⇒ ニュートラル状態

### RQ-02-04: 故障判定後条件 (Functional)
一度、故障と診断された後は再度ダイアグ判定を行わない

### RQ-02-03: 故障診断タイミング (Functional)
ダイアグ判定を実施するタイミングは、ドアロック指令の変化から2秒後の時点とする

### RQ-02-02: 故障判定条件 (Functional)
以下の表に応じて診断結果を判定する。
| ロック制御指令値 | ドアロック状態 | 診断 |
| --- | --- | --- |
| ロック | ロック | OK |
|  | ロック以外 | NG |
| アンロック | アンロック | OK |
|  | アンロック以外 | NG |
